NIMBLE-TRAP-MIB DEFINITIONS ::= BEGIN

IMPORTS
    MODULE-IDENTITY, OBJECT-TYPE, NOTIFICATION-TYPE
        FROM SNMPv2-SMI
    DisplayString
        FROM SNMPv2-TC
    nimble
        FROM NIMBLE-MIB;

nimble-traps MODULE-IDENTITY
    LAST-UPDATED    "201406130000Z"
    ORGANIZATION    "Nimble Storage, Inc."
    CONTACT-INFO
            "Nimble Storage

            support@nimblestorage.com"
    DESCRIPTION
        "Alert SMI Information for Nimble"

    REVISION    "201406130000Z"
    DESCRIPTION "Nimble Storage 2.2.0.0 Trap MIB"
    REVISION    "201405090000Z"
    DESCRIPTION "Nimble Storage 2.0.8.0 Trap MIB"
    REVISION    "201207120000Z"
    DESCRIPTION "Nimble Storage 1.4.0.0 Trap MIB"
    REVISION    "201206120000Z"
    DESCRIPTION "Initial revision"
    ::= { nimble 2 }

--
-- Nimble traps (which are actually SNMP Notifications)
--

trapObjects OBJECT IDENTIFIER ::= { nimble-traps 1 }

trapvariables OBJECT IDENTIFIER ::= { trapObjects 1 }

trapMsg OBJECT-TYPE
    SYNTAX  DisplayString (SIZE(0..255))
    MAX-ACCESS  read-only
    STATUS      current
    DESCRIPTION
    "Message string. This is the full text of the alert message."
::= { trapvariables 1 }

trapSeverity OBJECT-TYPE
    SYNTAX  DisplayString
    MAX-ACCESS  read-only
    STATUS      current
    DESCRIPTION
    "The severity level of the trap (informational, notice, warning, error, critical)."
::= { trapvariables 2 }

trapOriginatorName OBJECT-TYPE
    SYNTAX  DisplayString
    MAX-ACCESS  read-only
    STATUS      current
    DESCRIPTION
    "The array name that originated the trap."
::= { trapvariables 3 }

trapOriginatorSerialNumber OBJECT-TYPE
    SYNTAX  DisplayString
    MAX-ACCESS  read-only
    STATUS      current
    DESCRIPTION
    "The serial number of the array that originated the trap."
::= { trapvariables 4 }

trapOriginatorGroupName OBJECT-TYPE
    SYNTAX  DisplayString
    MAX-ACCESS  read-only
    STATUS      current
    DESCRIPTION
    "The name of the group that originated the trap."
::= { trapvariables 5 }

trapOriginatorGroupID OBJECT-TYPE
    SYNTAX  DisplayString
    MAX-ACCESS  read-only
    STATUS      current
    DESCRIPTION
    "The ID of the group that originated the trap."
::= { trapvariables 6 }

trapTarget OBJECT-TYPE
    SYNTAX  DisplayString
    MAX-ACCESS  read-only
    STATUS      current
    DESCRIPTION
    "The object for which this trap was generated."
::= { trapvariables 7 }

trapTargetType OBJECT-TYPE
    SYNTAX  DisplayString
    MAX-ACCESS  read-only
    STATUS      current
    DESCRIPTION
    "The type of object for which this trap was generated."
::= { trapvariables 8 }


traps OBJECT IDENTIFIER ::= { trapObjects 2 }


nimbleDsdRedEntry0101Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Low writable space"
::= { traps 65 }

nimbleDsdGcBehindSpaceRedExit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Writable space reclaimed"
::= { traps 66 }

nimbleDsdSpaceCrit0103Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Critically low writable space"
::= { traps 67 }

nimbleDsdSpaceUtilizationHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High system utilization"
::= { traps 68 }

nimbleDsdSpaceUtilizationOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System utilization OK"
::= { traps 69 }

nimbleDsdSpaceUtilizationCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically high system utilization"
::= { traps 70 }

nimbleDsdSpaceRedEntry0107Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Critically low writable space"
::= { traps 71 }

nimbleDsdSpaceCrit0110Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Critically low writable space"
::= { traps 72 }

nimbleDsdGcBehindSpaceRedEntry NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically low writable space"
::= { traps 73 }

nimbleDsdGcBehindSpaceCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically low writable space"
::= { traps 74 }

nimbleDsdSpaceDenyWrite NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically high system utilization"
::= { traps 75 }

nimbleDsdSpaceRedEntry NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically low space"
::= { traps 76 }

nimbleDsdSpaceRedExit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Writable space sufficiently restored"
::= { traps 77 }

nimbleDsdSpaceCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically low space"
::= { traps 78 }

nimbleDsdSnapshotReachingInfoLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Writable snapshot count approaching limit"
::= { traps 79 }

nimbleDsdSnapshotReachingWarningLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Writable snapshot count over warning limit"
::= { traps 80 }

nimbleDsdSnapshotCriticalLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Writable snapshot count over critical limit"
::= { traps 81 }

nimbleDsdSnapshotBelowCriticalLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Writable snapshot count is back below critical limit"
::= { traps 82 }

nimbleCtrlrException NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unhandled controller exception"
::= { traps 2001 }

nimbleCtrlrTakeover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller takeover occurred"
::= { traps 2002 }

nimbleCtrlrStandbyAvail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller available"
::= { traps 2003 }

nimbleCtrlrStandbyUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller not available"
::= { traps 2004 }

nimbleCtrlrExcessiveRestarts NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive controller restarts detected"
::= { traps 2005 }

nimbleServiceReboot NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Restarting controller to recover service"
::= { traps 2006 }

nimbleUserReboot NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Rebooting controller on user request"
::= { traps 2007 }

nimbleUserRebootFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to reboot controller per user request"
::= { traps 2008 }

nimbleUserHalt NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Halting controller on user request"
::= { traps 2009 }

nimbleUserHaltFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to halt controller per user request"
::= { traps 2010 }

nimbleCtrlrStandbyUnavailInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller not available"
::= { traps 2011 }

nimbleCtrlrStandbyUnavailWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller not available for an extended period"
::= { traps 2012 }

nimbleCtrlrExceptionWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unhandled controller exception"
::= { traps 2013 }

nimbleCtrlrExceptionCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unhandled controller exception"
::= { traps 2014 }

nimbleCtrlrStandbyUnavailWarnTimeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Standby controller not available for an extended period"
::= { traps 2015 }

nimbleCtrlrStandbyUnavailWarnTime NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller not available for an extended period"
::= { traps 2016 }

nimbleCtrlrTakeoverWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller takeover occurred"
::= { traps 2017 }

nimbleCtrlrFailoverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Controller failover occurred"
::= { traps 2018 }

nimbleCtrlrFailoverDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Controller failover occurred"
::= { traps 2019 }

nimbleCtrlrWatchdogDisabled NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller running with watchdog disabled"
::= { traps 2020 }

nimbleCtrlrFailover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller failover occurred"
::= { traps 2021 }

nimbleCtrlrFailoverAttempt NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Attempting controller failover"
::= { traps 2022 }

nimbleCtrlrFailoverFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller could not complete failover"
::= { traps 2023 }

nimbleCtrlrFailoverSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller failover occurred"
::= { traps 2024 }

nimbleCtrlrRaidAssemblyErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller missing too many drives and cannot failover"
::= { traps 2025 }

nimbleCtrlrRaidAssemblyDeg NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Standby controller performance degraded on failover; missing afs"
::= { traps 2026 }

nimbleCtrlrDegradedMode NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive controller restarts detected"
::= { traps 2027 }

nimbleCtrlrRebootUnexpected NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller rebooted unexpectedly"
::= { traps 2028 }

nimbleUserHaltArrayFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to halt array per user request"
::= { traps 2029 }

nimbleUserRebootArrayFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to reboot array per user request"
::= { traps 2030 }

nimbleUserHaltArrayFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to halt array per user request"
::= { traps 2031 }

nimbleUserRebootArrayFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to reboot array per user request"
::= { traps 2032 }

nimbleServiceStarted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service started"
::= { traps 2101 }

nimbleServiceDeadRestart NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service stopped unexpectedly"
::= { traps 2102 }

nimbleServiceDeadNoRestart NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service stopped unexpectedly"
::= { traps 2103 }

nimbleServiceCreateTunnelDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Created secure tunnel to Nimble Storage support"
::= { traps 2104 }

nimbleServiceTerminateTunnelDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Tunnel to Nimble Storage support has been terminated"
::= { traps 2105 }

nimbleServiceEssentialStoppedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Service stopped unexpectedly"
::= { traps 2106 }

nimbleServiceEssentialStopped NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service stopped unexpectedly"
::= { traps 2107 }

nimbleServiceEmailAlertFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to send alert e-mail"
::= { traps 2108 }

nimbleServiceEmailAlertFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to send alert e-mail"
::= { traps 2109 }

nimbleServiceManuallyDisabled NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service manually disabled"
::= { traps 2110 }

nimbleServiceCreateTunnel NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Created secure tunnel to {support}"
::= { traps 2111 }

nimbleServiceTerminateTunnel NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Tunnel to {support} has been terminated"
::= { traps 2112 }

nimbleDnsResolutionFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unable to resolve known support hosts due to DNS lookup failure."
::= { traps 2113 }

nimbleServiceMemLimitViolation NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Service violated memory limit"
::= { traps 2114 }

nimbleTestDbg NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5000 }

nimbleTestInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5001 }

nimbleTestErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5002 }

nimbleTestNot NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5003 }

nimbleTestNoteDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Test alert"
::= { traps 5004 }

nimbleTestWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5005 }

nimbleTestCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5006 }

nimbleTestNote NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Test alert"
::= { traps 5007 }

nimbleUpdateUnpackFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unpacking update package failed"
::= { traps 6000 }

nimbleUpdateStartedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Software update started"
::= { traps 6001 }

nimbleUpdateRevert NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Reverting software to previous version"
::= { traps 6002 }

nimbleUpdateSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Successfully updated software"
::= { traps 6003 }

nimbleUpdateRollback NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Rolling back software"
::= { traps 6004 }

nimbleUpdatePrecheckFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Update package pre-check failed"
::= { traps 6005 }

nimbleUpdateFailMsg NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed"
::= { traps 6007 }

nimbleUpdateUnpackStarted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unpacking update package"
::= { traps 6008 }

nimbleUpdateUnpackDone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unpacked update package"
::= { traps 6009 }

nimbleUpdateSwitchRoot NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update reboot"
::= { traps 6010 }

nimbleUpdateDownloadFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to download software update package"
::= { traps 6011 }

nimbleUpdateFailTmpFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. /tmp is full"
::= { traps 6012 }

nimbleUpdateFailScratchFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. scratch space is full"
::= { traps 6013 }

nimbleUpdateFailVarFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. /var is full"
::= { traps 6014 }

nimbleUpdateFailConfigFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. Configuration space is full"
::= { traps 6015 }

nimbleUpdateFailUsbFsFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update failed. Recovery OS space is full"
::= { traps 6016 }

nimbleUpdatePkgNotFound NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update package was not found"
::= { traps 6017 }

nimbleUpdatePkgWrongSig NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update package has wrong signature"
::= { traps 6018 }

nimbleUpdatePkgWrongCksum NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update package has wrong checksum"
::= { traps 6019 }

nimbleUpdateNetDegradeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Software update precheck failed. Network connectivity will degrade after software update"
::= { traps 6020 }

nimbleUpdateDisallowSoloDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Software update failed. Update cannot be applied while services cannot be failed over to other controller"
::= { traps 6021 }

nimbleUpdateDisallowSolo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update cannot be applied."
::= { traps 6022 }

nimbleUpdateNetDegrade NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update precheck failed. Network connectivity will degrade after software update"
::= { traps 6023 }

nimbleUpdateRaidDegrade NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update precheck failed. RAID assembly failed on standby controller and prevents software update to proceed"
::= { traps 6024 }

nimbleUpdateStarted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update started"
::= { traps 6025 }

nimbleUpdateSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Successfully updated software"
::= { traps 6026 }

nimbleUpdatePkgSignatureCheckFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update package signature check failure"
::= { traps 6027 }

nimbleUpdatePkgMalformed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update package header malformed"
::= { traps 6028 }

nimbleUpdateMultipleBootdev NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update precheck failed. Multiple boot devices detected"
::= { traps 6029 }

nimbleDownloadDnsFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software download failed due to DNS errors"
::= { traps 6401 }

nimbleAutoDownloadFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software auto-download failed"
::= { traps 6402 }

nimbleAutoDownloadSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software auto-download succeeded"
::= { traps 6403 }

nimbleUpdateArrayUnreachable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to contact a member array during software update"
::= { traps 6501 }

nimbleUpdateArrayFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to update software on a member array"
::= { traps 6502 }

nimbleUpdateArrayTimedOut NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Software update on a member array timed out"
::= { traps 6503 }

nimbleUpdateIqnConflict NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Removed conflicting IQN that was added during software upgrade"
::= { traps 6504 }

nimbleUpdateNwtVersionOutdated NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The version of NWT installed must be updated."
::= { traps 6505 }

nimbleArrayUnreachableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "A member array became unreachable"
::= { traps 10010 }

nimbleArrayReachableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "A member array became reachable"
::= { traps 10011 }

nimbleArrayUnreachable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "A member array is unreachable"
::= { traps 10012 }

nimbleArrayReachable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "A member array is reachable"
::= { traps 10013 }

nimbleUserClearedSysCacheDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Cache cleared by user"
::= { traps 10101 }

nimbleHostTypeMisconfiguredDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Detected conflicting host types"
::= { traps 10102 }

nimbleHostTypeMisconfigured NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Detected conflicting host types"
::= { traps 10103 }

nimbleVolSpcCurWarningUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage over warning limit"
::= { traps 10200 }

nimbleVolSpcCurWarningDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage below warning limit"
::= { traps 10201 }

nimbleVolSpcCurQuotaUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage over quota"
::= { traps 10202 }

nimbleVolSpcCurQuotaDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage below quota"
::= { traps 10203 }

nimbleVolSpcSnapWarningUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage over warning limit"
::= { traps 10204 }

nimbleVolSpcSnapWarningDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage below warning limit"
::= { traps 10205 }

nimbleVolSpcSnapQuotaUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage over quota"
::= { traps 10206 }

nimbleVolSpcSnapQuotaDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage below quota"
::= { traps 10207 }

nimbleGmVolSpcCurCritUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage approaching quota"
::= { traps 10208 }

nimbleGmVolSpcCurCritDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage below critical limit"
::= { traps 10209 }

nimbleGmSnapSpcCurCritUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume snapshot space usage approaching quota"
::= { traps 10210 }

nimbleGmSnapSpcCurCritDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume snapshot space usage below critical limit"
::= { traps 10211 }

nimbleGmVolSpcCurQuotaOfflineDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume being taken offline because it is above its quota"
::= { traps 10212 }

nimbleGmVolSpcCurQuotaSetDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "The quota for volume is being set to 100% because it is above its current quota"
::= { traps 10213 }

nimbleGmVolSpcSnapQuotaOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being taken offline because it is above its snapshot quota"
::= { traps 10214 }

nimbleGmVolSpcSnapQuotaSet NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The snapshot quota for volume is being set to unlimited because it is above its snapshot quota"
::= { traps 10215 }

nimbleGmVolSpcCurReserveOfflineDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume being taken offline because it is above its reserve and system is out of free space"
::= { traps 10216 }

nimbleGmVolSpcCurReserveSetDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume reserve is being set to zero because it is above its reserve and system is out of free space"
::= { traps 10217 }

nimbleGmVolSpcSnapReserveOfflineDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume being taken offline because it is above its snapshot reserve and system is out of free space"
::= { traps 10218 }

nimbleGmVolSpcSnapReserveSetDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume snapshot reserve is being set to zero because it is above its reserve and system is out of free space"
::= { traps 10219 }

nimbleGmVolSpcCurWarningUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage over warning limit"
::= { traps 10220 }

nimbleGmVolSpcCurWarningDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage below warning limit"
::= { traps 10221 }

nimbleGmVolSpcCurQuotaUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage is over the configured quota"
::= { traps 10222 }

nimbleGmVolSpcCurQuotaDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage is now below the configured quota"
::= { traps 10223 }

nimbleGmVolSpcSnapWarningUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage over warning limit"
::= { traps 10224 }

nimbleGmVolSpcSnapWarningDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume snapshot space usage below warning limit"
::= { traps 10225 }

nimbleGmVolSpcSnapQuotaUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume snapshot space usage over quota"
::= { traps 10226 }

nimbleGmVolSpcSnapQuotaDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume snapshot space usage below quota"
::= { traps 10227 }

nimbleVolAttrSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume attributes synchronization to arrays in the pool delayed"
::= { traps 10228 }

nimbleGmPoolArrAssgnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to assign array to pool"
::= { traps 10229 }

nimbleGmPoolArrUnassgnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to unassign array from pool"
::= { traps 10230 }

nimbleGmVolSpcCurCritUpUnlimDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage approaching quota"
::= { traps 10231 }

nimbleGmSnapSpcCurCritUpUnlimDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume snapshot space usage approaching quota"
::= { traps 10232 }

nimbleGmVolSpcReserveUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage is above its reserve"
::= { traps 10233 }

nimbleGmVolSpcReserveDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage is below its reserve"
::= { traps 10234 }

nimbleGmSnapSpcReserveUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume snapshot space usage is above its reserve"
::= { traps 10235 }

nimbleGmSnapSpcReserveDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume snapshot space usage is below its reserve"
::= { traps 10236 }

nimbleGmPoolMrgDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to merge pools."
::= { traps 10240 }

nimbleVolAttrSyncSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume attributes synchronization to arrays in the pool succeeded"
::= { traps 10241 }

nimbleSnapAttrSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Snapshot attributes synchronization to arrays in the pool delayed"
::= { traps 10242 }

nimbleSnapAttrSyncSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Snapshot attributes synchronization to arrays in the pool succeeded"
::= { traps 10243 }

nimbleGroupAttrSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Configuration synchronization to array delayed"
::= { traps 10244 }

nimbleGroupAttrSyncComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Configuration synchronization completed for array"
::= { traps 10245 }

nimbleGlCtrlrAttrSyncDelayDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader Platform Configuration synchronization is delayed"
::= { traps 10246 }

nimbleGlCtrlrAttrSyncCompleteDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader Configuration synchronization completed"
::= { traps 10247 }

nimbleGlCtrlrAttrSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Configuration synchronization to array delayed"
::= { traps 10248 }

nimbleGlCtrlrAttrSyncComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Configuration synchronization completed for array"
::= { traps 10249 }

nimbleVolMoveComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume completed move to destination pool"
::= { traps 10250 }

nimbleVolMoveAbortComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume completed aborting move to destination pool"
::= { traps 10251 }

nimbleGmPoolArrUnassgnCompleteDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Completed unassign of array from pool"
::= { traps 10252 }

nimbleGmPoolArrUnassgnComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Completed unassign of array from pool"
::= { traps 10253 }

nimbleGmPoolArrAssgn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to assign array to pool"
::= { traps 10256 }

nimbleGmPoolArrUnassgn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to unassign array from pool"
::= { traps 10257 }

nimbleGmPoolMrg NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to merge pools."
::= { traps 10260 }

nimbleGmVolSpcCurCritUpNonWritableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume space usage approaching volume quota"
::= { traps 10261 }

nimbleGmVolSpcCurQuotaNonWritableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume being set to non-writable because it is above its volume quota"
::= { traps 10262 }

nimbleGmSnapSpcCurCritUpNonWritableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume snapshot space usage approaching snapshot quota"
::= { traps 10263 }

nimbleGmVolSpcSnapQuotaNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being set to non-writable because it is above its snapshot quota"
::= { traps 10264 }

nimbleGmVolSpcCurReserveNonWritableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume being set to non-writable because it is above its reserve and system is out of free space"
::= { traps 10265 }

nimbleGmVolSpcSnapReserveNonWritableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume being set to non-writable because it is above its snapshot reserve and system is out of free space"
::= { traps 10266 }

nimbleEncryptionNotActive NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption deactivated"
::= { traps 10267 }

nimbleEncryptionMasterKeyRemoved NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption master key was deleted"
::= { traps 10268 }

nimbleEncryptionModeSecured NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption mode was changed to secure mode"
::= { traps 10269 }

nimbleEncryptionModeAvailable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption mode was changed to available mode"
::= { traps 10270 }

nimbleEncryptionMasterKeyCreated NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption master key was created"
::= { traps 10271 }

nimbleEncryptionPassphraseModified NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption passphrase was changed"
::= { traps 10272 }

nimbleEncryptionCipherModified NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption cipher was changed"
::= { traps 10273 }

nimbleEncryptionScopeModified NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption scope was changed"
::= { traps 10274 }

nimbleEncryptionActive NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption activated"
::= { traps 10275 }

nimbleEncryptionSlow NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encrypted volume access may be slow"
::= { traps 10276 }

nimbleEncryptionActiveMasterKeyRemoved NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption master key was deleted"
::= { traps 10277 }

nimbleGmVolSerialCollisionOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Invalid volume serial number detected"
::= { traps 10278 }

nimbleGmSnapSerialCollisionOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Invalid snapshot serial number detected"
::= { traps 10279 }

nimbleIgrpSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Initiator group synchronization is delayed to arrays in the group"
::= { traps 10280 }

nimbleIgrpSyncSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Initiator group synchronization to arrays in the group succeeded"
::= { traps 10281 }

nimbleGmPinCacheInsufficientDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Insufficient cache capacity in the pool for cache pinned volumes"
::= { traps 10282 }

nimbleFolderAttrSyncDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Folder attributes synchronization to arrays in the pool delayed"
::= { traps 10283 }

nimbleFolderAttrSyncSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Folder attributes synchronization to arrays in the pool succeeded"
::= { traps 10284 }

nimbleGmVolFolderLimitOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being taken offline because folder usage is over the folder overdraft limit"
::= { traps 10285 }

nimbleGmVolFolderLimitNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being set to non-writable because folder usage is over the folder overdraft limit"
::= { traps 10286 }

nimbleGmFolderUsedSpaceUtilizationCritDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Critically high folder space utilization"
::= { traps 10287 }

nimbleGmFolderUsedSpaceUtilizationHighDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "High folder space utilization"
::= { traps 10288 }

nimbleGmFolderUsedSpaceUtilizationInfoDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "High folder space utilization"
::= { traps 10289 }

nimbleGmFolderUsedSpaceUtilizationOkDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Folder space utilization OK"
::= { traps 10290 }

nimbleGmFolderUsedSpaceReplicationStopped NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Folder usage over usage limit and replication has stopped"
::= { traps 10291 }

nimbleGmFolderUsedSpaceReplicationStoppedUpstreamDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Folder usage over usage limit and replication has stopped"
::= { traps 10292 }

nimbleGmFolderUsedSpaceReplicationOkDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Folder space utilization below usage limit"
::= { traps 10293 }

nimbleGmVolSpcCurProvisionOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being taken offline because it is thinly provisioned and the pool is out of free space"
::= { traps 10294 }

nimbleGmVolSpcCurProvisionNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being set to non-writable because it is thinly provisioned and the pool is out of free space"
::= { traps 10295 }

nimbleVolReserveConversionToProvisioningLevel NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume reserve has been converted to provisioning level due to software upgrade"
::= { traps 10296 }

nimbleGmFolderUsedSpaceUtilizationCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically high folder space utilization"
::= { traps 10297 }

nimbleGmFolderUsedSpaceUtilizationHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High folder space utilization"
::= { traps 10298 }

nimbleGmFolderUsedSpaceUtilizationInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Folder space utilization near warning levels"
::= { traps 10299 }

nimbleGmFolderUsedSpaceUtilizationOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Folder space utilization OK"
::= { traps 10600 }

nimbleGmFolderUsedSpaceReplicationStoppedUpstreamDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Downstream folder usage over usage limit and replication has stopped"
::= { traps 10601 }

nimbleGmFolderUsedSpaceReplicationOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Folder space utilization below usage limit and replication has resumed"
::= { traps 10602 }

nimbleGmFolderUsedSpaceReplicationStoppedUpstream NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Downstream folder usage over usage limit and replication has stopped"
::= { traps 10603 }

nimbleSchedSnapSucceededDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot succeeded"
::= { traps 10300 }

nimbleSchedSnapFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot failed"
::= { traps 10301 }

nimbleSchedSnapSkippedExists NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot skipped"
::= { traps 10302 }

nimbleSchedSnapSkippedHandover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot skipped"
::= { traps 10303 }

nimbleSchedSnapSucceededLagInfoDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot succeeded"
::= { traps 10304 }

nimbleSchedSnapFailedVmwareCredentialDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10305 }

nimbleSchedSnapFailedVmwareConnectionTimeoutDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10306 }

nimbleSchedSnapFailedVmwareConnectionRefusedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10307 }

nimbleSchedSnapFailedVmwareConnectionResetDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10308 }

nimbleSchedSnapFailedVmwareConnectionNorouteDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10309 }

nimbleSchedSnapFailedVmwareConnectionSocketDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10310 }

nimbleSchedSnapFailedVmwareConnectionUnreachableDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10311 }

nimbleSchedSnapFailedVmwareDisabledDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10312 }

nimbleSchedSnapFailedVmwareObjectnfDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10313 }

nimbleSchedSnapFailedVmwarePermissionDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10314 }

nimbleSchedSnapFailedVmwareUkhostDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10315 }

nimbleSchedSnapFailedVmwareEncodingPlainDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10316 }

nimbleSchedSnapFailedVmwareNullDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10317 }

nimbleSchedSnapFailedVmwareDcnotfoundDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10318 }

nimbleSchedSnapFailedVmwareVolsnemptyDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10319 }

nimbleSchedSnapFailedVmwareUnknownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10320 }

nimbleSchedSnapFailedVmwareBsizeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot succeeded with warning"
::= { traps 10321 }

nimbleSchedSnapSucceeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot succeeded"
::= { traps 10322 }

nimbleSchedSnapSucceededLagInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot succeeded"
::= { traps 10323 }

nimbleSchedSnapFailedVmwareDisabledDeprecatedTwo NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10324 }

nimbleSchedSnapFailedVmwareTimeoutDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10325 }

nimbleSchedSnapFailedVmwareSnapNameMaxLengthExceededDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 10326 }

nimbleSchedSnapFallback NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Application synchronization failed"
::= { traps 10327 }

nimbleSchedSnapFailedUnknownReason NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot failed."
::= { traps 10328 }

nimbleSchedSnapFailedVmwarePermissionPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10340 }

nimbleSchedSnapFailedVmwareObjectnfPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10341 }

nimbleSchedSnapFailedVmwareEncodingPlainPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10342 }

nimbleSchedSnapFailedVmwareNullPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10343 }

nimbleSchedSnapFailedVmwareDcnotfoundPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10344 }

nimbleSchedSnapFailedVmwareVolsnemptyPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10345 }

nimbleSchedSnapFailedVmwareUnknownPerVmDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Failed to synchronize with VMware vCenter"
::= { traps 10346 }

nimbleSchedSnapFailedVmwareBsizePerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10347 }

nimbleSchedSnapFailedVmwareDisabledPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10348 }

nimbleSchedSnapFailedVmwareTimeoutPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10349 }

nimbleSchedSnapFailedVmwareSnapNameMaxLengthExceededPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10350 }

nimbleSchedSnapFailedVmwareGuestToolsNotRunningPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10351 }

nimbleSchedSnapFailedVmwareInvalidVcenter NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10352 }

nimbleSchedSnapFailedVmwareBusy NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10353 }

nimbleSchedSnapFailedVssIncompatible NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot failed"
::= { traps 10354 }

nimbleSchedSnapFailedVmwareCredentialNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10355 }

nimbleSchedSnapFailedVmwareConnectionTimeoutNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10356 }

nimbleSchedSnapFailedVmwareConnectionRefusedNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10357 }

nimbleSchedSnapFailedVmwareConnectionResetNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10358 }

nimbleSchedSnapFailedVmwareConnectionNorouteNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10359 }

nimbleSchedSnapFailedVmwareConnectionSocketNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10360 }

nimbleSchedSnapFailedVmwareConnectionUnreachableNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10361 }

nimbleSchedSnapFailedVmwareUkhostNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10362 }

nimbleSchedSnapFailedVmwareConnectionUnknownNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10363 }

nimbleSchedSnapFailedVmwareTimeoutNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10364 }

nimbleSchedSnapFailedVmwareUnknownNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10365 }

nimbleSchedSnapFailedVmwareUnknownPerVm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10366 }

nimbleSchedSnapFailedVmwareQuiescingVmFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10367 }

nimbleSchedSnapFailedVmwareLeftoverSnapshot NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with VMware vCenter"
::= { traps 10368 }

nimbleSchedSnapFailedGenericConnectionTimeoutNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10370 }

nimbleSchedSnapFailedGenericConnectionNorouteNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10371 }

nimbleSchedSnapFailedGenericConnectionRefusedNw  NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10372 }

nimbleSchedSnapFailedGenericConnectionSocketNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10373 }

nimbleSchedSnapFailedGenericCredentialNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10374 }

nimbleSchedSnapFailedGenericUkhostNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10375 }

nimbleSchedSnapFailedGenericConnectionUnknownNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10376 }

nimbleSchedSnapFailedGenericAgentError NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10377 }

nimbleSchedSnapFailedGenericTimeoutNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10378 }

nimbleSchedSnapFailedGenericBusy NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10379 }

nimbleSchedSnapFailedVssWriterFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled VSS snapshot failed."
::= { traps 10380 }

nimbleSchedSnapFailedVssNonTerminatingWriterFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "VSS synchronization failed for some of the application objects."
::= { traps 10381 }

nimbleSchedSnapFailedVssVolcollConfigError NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled VSS snapshot failed."
::= { traps 10382 }

nimbleSchedSnapFailedVssSnapVerificationError NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled VSS snapshot failed."
::= { traps 10383 }

nimbleSchedSnapFailedVssPreviousSnapInProgress NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled VSS snapshot failed."
::= { traps 10384 }

nimbleSchedSnapFailedVssSnapFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled VSS snapshot failed."
::= { traps 10385 }

nimbleSchedSnapFailedVssBadCookie NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled VSS snapshot failed."
::= { traps 10386 }

nimbleSchedSnapFailedGenericUnknownNw NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to synchronize with backup agent"
::= { traps 10387 }

nimbleVssVolcollConfigWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection configuration warning."
::= { traps 10388 }

nimbleDhciUpdateFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "dHCI update failed."
::= { traps 10393 }

nimbleDhciUpdateResumed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "dHCI update resumed back."
::= { traps 10394 }

nimbleDhciUpdateSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "dHCI update completed successfully."
::= { traps 10395 }

nimbleApplicationServerLoginFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Login to application server failed"
::= { traps 10396 }

nimbleApplicationServerLoginSucceeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Login to application server succeeded"
::= { traps 10397 }

nimbleVvolManagementConnectionDisrupted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "VVol management connection has been disrupted."
::= { traps 10398 }

nimbleVvolManagementConnectionReestablished NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "VVol management connection has been re-established."
::= { traps 10399 }

nimbleGmSpaceReserveWarnUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space above warning limit"
::= { traps 10401 }

nimbleGmSpaceReserveWarnDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space below warning limits"
::= { traps 10402 }

nimbleGmSpaceReserveCritUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space above critical level"
::= { traps 10403 }

nimbleGmSpaceReserveCritDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space below critical limits"
::= { traps 10404 }

nimbleGmSpaceUtilizationOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array space utilization OK"
::= { traps 10405 }

nimbleGmSpaceUtilizationInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High array space utilization"
::= { traps 10406 }

nimbleGmSpaceUtilizationHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High array space utilization"
::= { traps 10407 }

nimbleGmSpaceUtilizationCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically high array space utilization"
::= { traps 10408 }

nimbleGmPoolSpaceReserveWarnUpDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool above warning limit"
::= { traps 10409 }

nimbleGmPoolSpaceReserveWarnDownDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool below warning limits"
::= { traps 10410 }

nimbleGmPoolSpaceReserveCritUpDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool above critical level"
::= { traps 10411 }

nimbleGmPoolSpaceReserveCritDownDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool below critical limits"
::= { traps 10412 }

nimbleGmPoolSpaceUtilizationOkDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Pool space utilization OK"
::= { traps 10413 }

nimbleGmPoolSpaceUtilizationInfoDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "High pool space utilization"
::= { traps 10414 }

nimbleGmPoolSpaceUtilizationHighDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "High pool space utilization"
::= { traps 10415 }

nimbleGmPoolSpaceUtilizationCritDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Critically high pool space utilization"
::= { traps 10416 }

nimbleGmPoolSpaceReserveWarnUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool above warning limit"
::= { traps 10417 }

nimbleGmPoolSpaceReserveWarnDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool below warning limits"
::= { traps 10418 }

nimbleGmPoolSpaceReserveCritUpDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool above critical level"
::= { traps 10419 }

nimbleGmPoolSpaceReserveCritDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool below critical limits"
::= { traps 10420 }

nimbleGmPoolSpaceUtilizationOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Pool space utilization OK"
::= { traps 10421 }

nimbleGmPoolSpaceUtilizationInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High pool space utilization"
::= { traps 10422 }

nimbleGmPoolSpaceUtilizationHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "High pool space utilization"
::= { traps 10423 }

nimbleGmPoolSpaceUtilizationCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Critically high pool space utilization"
::= { traps 10424 }

nimbleGmVolSpcCurCritUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage approaching limit"
::= { traps 10427 }

nimbleGmVolSpcCurCritDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage below critical limit"
::= { traps 10428 }

nimbleGmVolSpcCurLimitOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being taken offline because it is above its limit"
::= { traps 10429 }

nimbleGmVolSpcCurLimitUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage is over the configured limit"
::= { traps 10430 }

nimbleGmVolSpcCurLimitDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage is now below the configured limit"
::= { traps 10431 }

nimbleGmVolSpcCurCritUpUnlim NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage approaching limit"
::= { traps 10432 }

nimbleGmVolSpcCurCritUpNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume space usage approaching volume limit"
::= { traps 10433 }

nimbleGmVolSpcCurLimitNonWritable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume being set to non-writable because it is above its volume limit"
::= { traps 10434 }

nimbleGmPoolSpaceProvisionWarnUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space in the pool above warning limit"
::= { traps 10435 }

nimbleGmPoolSpaceProvisionWarnDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space in the pool below warning limits"
::= { traps 10436 }

nimbleGmPoolSpaceProvisionCritUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space in the pool above critical level"
::= { traps 10437 }

nimbleGmPoolSpaceProvisionCritDownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Used space in the pool below critical limits"
::= { traps 10438 }

nimbleGmPoolSpaceProvisionCritDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Used space in the pool below critical limits"
::= { traps 10439 }

nimbleLimitMaxOverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Object count reached maximum limit"
::= { traps 10500 }

nimbleLimitMaxUnderDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Object count under maximum limit"
::= { traps 10501 }

nimbleLimitWarnOverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Object count over warning limit"
::= { traps 10502 }

nimbleLimitWarnUnderDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Object count under warning limit"
::= { traps 10503 }

nimbleLimitMaxOverWithContextDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Object count reached maximum limit."
::= { traps 10504 }

nimbleLimitMaxUnderWithContextDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Object count under maximum limit."
::= { traps 10505 }

nimbleLimitWarnOverWithContextDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Object count over warning threshold."
::= { traps 10506 }

nimbleLimitWarnUnderWithContextDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Object count under warning threshold."
::= { traps 10507 }

nimbleLimitMaxOver NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count reached maximum limit"
::= { traps 10510 }

nimbleLimitMaxUnder NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count under maximum limit"
::= { traps 10511 }

nimbleLimitWarnOver NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count over warning limit"
::= { traps 10512 }

nimbleLimitWarnUnder NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count under warning limit"
::= { traps 10513 }

nimbleLimitMaxOverWithContext NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count reached maximum limit."
::= { traps 10514 }

nimbleLimitMaxUnderWithContext NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count under maximum limit."
::= { traps 10515 }

nimbleLimitWarnOverWithContext NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count over warning threshold."
::= { traps 10516 }

nimbleLimitWarnUnderWithContext NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Object count under warning threshold."
::= { traps 10517 }

nimbleGroupTimeSkew NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "A time skew occurred between the array and NTP server"
::= { traps 10518 }

nimbleReplSnapcollSucceeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication succeeded"
::= { traps 11000 }

nimbleReplSnapcollDelayedInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive replication delay"
::= { traps 11001 }

nimbleReplSnapcollDelayedWarnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Excessive replication delay"
::= { traps 11002 }

nimbleReplPartnerSyncFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Partner synchronization failed"
::= { traps 11003 }

nimbleReplBranchPinned NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume replication stalled"
::= { traps 11004 }

nimbleReplHandoverCompletedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume collection handover completed"
::= { traps 11005 }

nimbleReplMultiArrayGroup NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication between multi-array scaleout group and pre-scaleout array is not supported"
::= { traps 11006 }

nimbleReplPartnerMisconfiguration NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication between a scaleout group and pre-scaleout array must be configured over the management network"
::= { traps 11007 }

nimbleReplSnapshotCorrectedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Replication resynchronized"
::= { traps 11008 }

nimbleReplCbrRequestedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Resynchronization not supported"
::= { traps 11009 }

nimbleReplCbrNeeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Resynchronization not supported"
::= { traps 11010 }

nimbleReplSnapshotCorrectedDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Replication resynchronized"
::= { traps 11011 }

nimbleReplCbrRequestedDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Resynchronization not supported"
::= { traps 11012 }

nimbleReplPartnerAuthFailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Partner authentication failed"
::= { traps 11013 }

nimbleReplSnapshotCorrected NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated snapshot resynchronized"
::= { traps 11014 }

nimbleReplCbrRequested NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated snapshot resynchronization not supported"
::= { traps 11015 }

nimbleReplPartnerAuthFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication partner authentication failed"
::= { traps 11016 }

nimbleReplVolumeResynchronize NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated volume needs resynchronization"
::= { traps 11017 }

nimbleReplHandoverAbortedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume collection handover aborted"
::= { traps 11018 }

nimbleReplHandoverCompletedOfflineDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume collection handover completed with errors."
::= { traps 11019 }

nimbleReplHandoverAbortedOfflineDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume collection handover aborted with errors."
::= { traps 11020 }

nimbleReplProtpolDeletionFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume collection could not be deleted on the downstream replication partner."
::= { traps 11021 }

nimbleReplBranchpointTrimmedNocommonDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Replication of volume is stalled due to space reclamation."
::= { traps 11022 }

nimbleReplBranchpointTrimmedCommonDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Replication of volume is stalled due to space reclamation on common snapshot."
::= { traps 11023 }

nimbleReplVolumeAutoResynchronize NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated volume needs resynchronization"
::= { traps 11024 }

nimbleReplVolumeCorrectedNoErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated volume resynchronized"
::= { traps 11025 }

nimbleReplPartnerUnsupportedVssAppId NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication is not supported on the partner for the VSS application ID"
::= { traps 11026 }

nimbleReplBranchInconsistentDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Replicated volume will be resynchronized"
::= { traps 11027 }

nimbleReplPoolPartnerCreated NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Pool partner creation succeeded"
::= { traps 11028 }

nimbleReplPartnerOosyncDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "The partner is out of sync with the downstream replica"
::= { traps 11031 }

nimbleReplPartnerInsyncDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "The partner is in sync with the downstream replica"
::= { traps 11032 }

nimbleReplVolcolOosyncDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Some volume collections are out of sync with their downstream replicas"
::= { traps 11033 }

nimbleReplVolcolInsyncDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "The volume collection is in sync with the downstream replica"
::= { traps 11034 }

nimbleReplSrepVolumeHasAcls NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration of downstream volume failed due to existing ACLs"
::= { traps 11035 }

nimbleReplSrepVolumeAclsRemovedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "All ACLs for downstream volume have been removed."
::= { traps 11036 }

nimbleReplSrepProtpolMgmtOosyncDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Due to manual takeover"
::= { traps 11037 }

nimbleReplPoolPartnerCreationFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Pool partner creation failed"
::= { traps 11038 }

nimbleReplSrepVolumeDnstrOnline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration of downstream volume failed because volume is online"
::= { traps 11039 }

nimbleReplSrepVolumeDnstrOfflineDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after offlining the downstream volume"
::= { traps 11040 }

nimbleReplSrepVolumeDnstrOnlineRenamedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after renaming the existing downstream volume"
::= { traps 11041 }

nimbleReplSrepVolumeDnstrSizeMismatch NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration of downstream volume failed because of size mismatch"
::= { traps 11042 }

nimbleReplSrepVolumeDnstrResized NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after resizing the downstream volume"
::= { traps 11043 }

nimbleReplSrepVolumeDnstrSizeMismatchDeletedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after deleting the existing downstream volume"
::= { traps 11044 }

nimbleReplSrepVolumeDnstrSizeMismatchRenamedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after renaming the existing downstream volume"
::= { traps 11045 }

nimbleReplSrepVolumeDnstrAgentTypeMismatch NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration of downstream volume failed because of agent type mismatch"
::= { traps 11046 }

nimbleReplSrepVolumeDnstrAgentTypeUpdated NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after updating agent type of downstream volume"
::= { traps 11047 }

nimbleReplSrepVolumeDnstrAgentTypeMismatchDeletedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after deleting the existing downstream volume"
::= { traps 11048 }

nimbleReplSrepVolumeDnstrAgentTypeMismatchRenamedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after renaming the existing downstream volume"
::= { traps 11049 }

nimbleReplSrepVolumeDnstrIscsiTargetScopeInvalidDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration of downstream volume failed because of incorrect iSCSI Target Scope"
::= { traps 11050 }

nimbleReplSrepVolumeDnstrIscsiTargetScopeUpdated NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after updating iSCSI Target Scope of downstream volume"
::= { traps 11051 }

nimbleReplSrepVolumeDnstrIscsiTargetScopeInvalidDeletedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after deleting the existing downstream volume"
::= { traps 11052 }

nimbleReplSrepVolumeDnstrIscsiTargetScopeInvalidRenamedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after renaming the existing downstream volume"
::= { traps 11053 }

nimbleReplSrepVolumeDnstrNoCommonSnap NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration of downstream volume failed because lack of common snapshot"
::= { traps 11054 }

nimbleReplSrepVolumeDnstrNoCommonSnapDeletedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after deleting the existing downstream volume"
::= { traps 11055 }

nimbleReplSrepVolumeDnstrNoCommonSnapRenamedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Synchronous replication configuration resumed after renaming the existing downstream volume"
::= { traps 11056 }

nimbleReplSrepAsoSwitchoverSuccessfulDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume collections were handed over because the upstream partner was not available"
::= { traps 11057 }

nimbleReplSrepAsoSwitchoverBlockedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Volume collections did not hand over because the downstream volumes are not in sync with the upstream volumes"
::= { traps 11058 }

nimbleReplSrepProtpolMgmtOosync NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Due to manual takeover"
::= { traps 11059 }

nimbleReplSrepVolumeDnstrOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after offlining the downstream volume"
::= { traps 11060 }

nimbleReplSrepVolumeDnstrOnlineRenamed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after renaming the existing downstream volume"
::= { traps 11061 }

nimbleReplSrepVolumeDnstrSizeMismatchDeleted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after deleting the existing downstream volume"
::= { traps 11062 }

nimbleReplSrepVolumeDnstrSizeMismatchRenamed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after renaming the existing downstream volume"
::= { traps 11063 }

nimbleReplSrepVolumeDnstrAgentTypeMismatchDeleted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after deleting the existing downstream volume"
::= { traps 11064 }

nimbleReplSrepVolumeDnstrAgentTypeMismatchRenamed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after renaming the existing downstream volume"
::= { traps 11065 }

nimbleReplSrepVolumeDnstrIscsiTargetScopeInvalid NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration of downstream volume failed because of incorrect iSCSI Target Scope"
::= { traps 11066 }

nimbleReplSrepVolumeDnstrIscsiTargetScopeInvalidDeleted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after deleting the existing downstream volume"
::= { traps 11067 }

nimbleReplSrepVolumeDnstrIscsiTargetScopeInvalidRenamed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after renaming the existing downstream volume"
::= { traps 11068 }

nimbleReplSrepVolumeDnstrNoCommonSnapDeleted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after deleting the existing downstream volume"
::= { traps 11069 }

nimbleReplSrepVolumeDnstrNoCommonSnapRenamed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration resumed after renaming the existing downstream volume"
::= { traps 11070 }

nimbleReplSrepAsoSwitchoverBlocked NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection handover could not be completed because the downstream volumes are not in sync with the upstream volumes"
::= { traps 11071 }

nimbleReplSrepVolumeAclsRemoved NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Synchronous replication configuration of downstream volume resumed after all ACLs were removed."
::= { traps 11072 }

nimbleReplPartnerOosyncDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "The partner is out of sync with the downstream replica"
::= { traps 11073 }

nimbleReplPartnerInsyncDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "The partner is in sync with the downstream replica"
::= { traps 11074 }

nimbleReplVolcolOosync NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Some volume collections are out of sync with their downstream replicas"
::= { traps 11075 }

nimbleReplVolcolInsync NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The volume collection is in sync with the downstream replica"
::= { traps 11076 }

nimbleReplSrepAsoSwitchoverSuccessful NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collections completed handover because the upstream partner was not available"
::= { traps 11077 }

nimbleReplSrepProtpolRecmFreqSchedMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection of type synchronous replication does not meet the recommended schedule of at least one replicated snapshot every few hours"
::= { traps 11080 }

nimbleReplSrepProtpolRecmFreqSchedImplemented NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection of type synchronous replication has schedules that meet the snapshot frequency recommendations"
::= { traps 11081 }

nimbleReplSrepProtpolRecmFreqNoReplVols NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection of type synchronous replication does not have any replicating volumes"
::= { traps 11082 }

nimbleReplBranchInconsistent NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated volume will be resynchronized"
::= { traps 11083 }

nimbleReplSnapshotCorrectedFromBranchInconsistency NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated snapshot resynchronized"
::= { traps 11084 }

nimbleReplSnapshotCorrectedFromBranchInconsistencyNoErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replicated snapshot resynchronized"
::= { traps 11085 }

nimbleReplSrepProtpolMgmtUnableToFindOosyncVolcolls NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Manual takeover of Group Leader detected"
::= { traps 11086 }

nimbleReplAtleastOneVolcollOosync NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The partner is out of sync with the downstream replica"
::= { traps 11087 }

nimbleReplAllVolcollsInsync NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The partner is in sync with the downstream replica"
::= { traps 11088 }

nimbleReplSnapcollDelayedWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive replication delay"
::= { traps 11089 }

nimbleReplStopped NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication of a volume collection has stopped"
::= { traps 11090 }

nimblePartnerPaused NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication has paused"
::= { traps 11091 }

nimbleReplHandoverCompleted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection handover completed"
::= { traps 11200 }

nimbleReplHandoverAborted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection handover aborted"
::= { traps 11201 }

nimbleReplHandoverCompletedOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection handover completed with errors."
::= { traps 11202 }

nimbleReplHandoverAbortedOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection handover aborted with errors."
::= { traps 11203 }

nimbleReplProtpolDeletionFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume collection could not be deleted on the downstream replication partner."
::= { traps 11204 }

nimbleReplBranchpointTrimmedNocommon NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication of the volume is stalled due to space reclamation."
::= { traps 11205 }

nimbleReplBranchpointTrimmedCommon NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication of the volume is stalled due to space reclamation on common snapshot."
::= { traps 11206 }

nimbleOvertempShutdownDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Overtemperature shutdown"
::= { traps 12000 }

nimbleCtrlrOvertempDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Controller overtemperature"
::= { traps 12001 }

nimbleBackplaneOvertempDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Backplane over-temperature"
::= { traps 12002 }

nimbleHsFlashSizeUnsupported NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Flash memory in head shelf does not meet the minimum requirement"
::= { traps 12003 }

nimbleHsFlashSizeNormal NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Flash memory in head shelf meets the minimum requirement"
::= { traps 12004 }

nimbleDiskFailedCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk failed"
::= { traps 12100 }

nimbleDiskFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk failed"
::= { traps 12101 }

nimbleDiskAbsent NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk missing"
::= { traps 12102 }

nimbleDiskAdded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk added"
::= { traps 12103 }

nimbleDiskRemoved NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk removed"
::= { traps 12104 }

nimbleSsdFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD failed"
::= { traps 12105 }

nimbleSsdAbsent NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD missing"
::= { traps 12106 }

nimbleSsdAdded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD added"
::= { traps 12107 }

nimbleSsdRemoved NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD removed"
::= { traps 12108 }

nimbleDiskInvalidLabel NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Foreign disk detected"
::= { traps 12109 }

nimbleSsdInvalidLabel NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Foreign SSD detected"
::= { traps 12110 }

nimbleDiskSizeMismatchDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Invalid disk size for this model"
::= { traps 12111 }

nimbleHddFailedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk failed"
::= { traps 12112 }

nimbleHddAbsentV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk missing"
::= { traps 12113 }

nimbleHddAddedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk added"
::= { traps 12114 }

nimbleHddRemovedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk removed"
::= { traps 12115 }

nimbleSsdFailedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD failed"
::= { traps 12116 }

nimbleSsdAbsentV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD missing"
::= { traps 12117 }

nimbleSsdAddedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD added"
::= { traps 12118 }

nimbleSsdRemovedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD removed"
::= { traps 12119 }

nimbleSsdLastOne NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Only one SSD drive left"
::= { traps 12120 }

nimbleHddFailedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk failed"
::= { traps 12121 }

nimbleHddAddedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk added"
::= { traps 12122 }

nimbleHddRemovedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk removed"
::= { traps 12123 }

nimbleSsdFailedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD failed"
::= { traps 12124 }

nimbleSsdAddedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD added"
::= { traps 12125 }

nimbleSsdRemovedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD removed"
::= { traps 12126 }

nimbleDiskSizeMismatchV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Invalid disk size for this shelf"
::= { traps 12127 }

nimbleSsdSizeMismatchV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Invalid SSD size for this shelf"
::= { traps 12128 }

nimbleHddFailedAfsDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Disk not supported on All Flash Shelf"
::= { traps 12129 }

nimbleHddFailedAfs NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk not supported on All-Flash Shelf"
::= { traps 12130 }

nimbleSsdNone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "No SSDs found"
::= { traps 12131 }

nimbleDiskMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk(s) inaccessible"
::= { traps 12132 }

nimbleDiskDiagRemoved NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk taken out of service for diagnosis"
::= { traps 12133 }

nimbleDfcSsdFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD failed"
::= { traps 12134 }

nimbleDfcSsdAdded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD added"
::= { traps 12135 }

nimbleDfcSsdRemoved NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD removed"
::= { traps 12136 }

nimbleDfcDiskSizeMismatch NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Invalid disk size for this shelf"
::= { traps 12137 }

nimbleDfcSsdSizeMismatch NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Invalid SSD size for this shelf"
::= { traps 12138 }

nimbleDfcHddFailedAfs NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk not supported on All-Flash Shelf"
::= { traps 12139 }

nimbleDfcDiskDiagRemoved NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk taken out of service for diagnosis"
::= { traps 12140 }

nimbleDfcSsdAbsent NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD missing"
::= { traps 12141 }

nimbleSsdAbsentV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSD missing"
::= { traps 12142 }

nimbleHddAbsentV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk missing"
::= { traps 12143 }

nimbleIposerFwUpdateStart NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Flash carrier firmware update started"
::= { traps 12144 }

nimbleIposerFwUpdateSucceed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Flash carrier firmware update succeeded"
::= { traps 12145 }

nimbleIposerFwUpdateFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Flash carrier firmware update failed"
::= { traps 12146 }

nimbleScmFailedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Storage Class Memory (SCM) failed"
::= { traps 12147 }

nimbleScmAddedV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Storage Class Memory (SCM) added"
::= { traps 12148 }

nimbleScmAbsentV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Storage Class Memory (SCM) missing"
::= { traps 12150 }

nimbleAfturboWithScm NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Storage Class Memory (SCM) acceleration"
::= { traps 12151 }

nimbleAfturboDegradeToAfa NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed Storage Class Memory (SCM) acceleration"
::= { traps 12152 }

nimbleScmHighTemperatureV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Storage Class Memory (SCM) temperature is too high"
::= { traps 12153 }

nimbleScmCrithighTemperatureV3 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Storage Class Memory (SCM) temperature is above the safe operating temperature"
::= { traps 12154 }

nimbleScmTemperatureCritOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Storage Class Memory (SCM) temperature below critical limit"
::= { traps 12155 }

nimbleScmTemperatureOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Storage Class Memory (SCM) temperature is ok"
::= { traps 12156 }

nimbleDiskSlowEarly NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Early stage slow drive detected"
::= { traps 12157 }

nimbleDiskSlowFatal NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Slow drive detected"
::= { traps 12158 }

nimbleScratchMountedReadonly NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scratch drive mounted R/O"
::= { traps 12159 }

nimbleScratchMountedReadwrite NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scratch drive mounted R/W"
::= { traps 12160 }

nimbleIpIfDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "IP interface down"
::= { traps 12200 }

nimbleIpIfUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "IP interface up"
::= { traps 12201 }

nimbleIpIfGroupUnavailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group IP interface unavailable"
::= { traps 12202 }

nimbleIpIfDataUnavailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "All Data IP interfaces unavailable"
::= { traps 12203 }

nimbleIpIfCantFailoverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "IP connectivity lost"
::= { traps 12204 }

nimbleSubnetNicMigrationDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Migrating subnet NIC configuration"
::= { traps 12205 }

nimbleSubnetNicMissingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NIC for subnet missing"
::= { traps 12206 }

nimbleIpNicMigrationDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Migrating IP NIC configuration"
::= { traps 12207 }

nimbleIpNicMissingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NIC for IP missing"
::= { traps 12208 }

nimbleRouteNicMigrationDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Migrating route NIC configuration"
::= { traps 12209 }

nimbleRouteNicMissingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NIC for route missing"
::= { traps 12210 }

nimbleIpIfFailoverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Standby controller has better network connectivity. Failing services over to standby controller"
::= { traps 12211 }

nimbleIpDupFoundDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Duplicate IP Address Detected"
::= { traps 12212 }

nimbleIpIfDiscoveryUnavailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Discovery IP interface unavailable"
::= { traps 12213 }

nimbleIpIfTargetUnavailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Target IP interfaces unavailable"
::= { traps 12214 }

nimbleIpIfGroupUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for Group IP interface(s)"
::= { traps 12215 }

nimbleIpIfDiscoveryUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for Discovery IP interface(s)"
::= { traps 12216 }

nimbleIpIfTargetUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for Target IP interface(s)"
::= { traps 12217 }

nimbleIpIfDataUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for Data IP interface(s)"
::= { traps 12218 }

nimbleIpIfIscsiDataUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for iSCSI Data IP interface(s)"
::= { traps 12219 }

nimbleIpIfClusterDataUnavail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Link down for cluster Data IP interface(s)"
::= { traps 12220 }

nimbleUnresponsiveNicDetected NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unresponsive NIC Port Detected"
::= { traps 12221 }

nimbleIpIfCantFailoverDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "IP connectivity lost"
::= { traps 12222 }

nimbleIpIfCantFailover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Network connectivity lost"
::= { traps 12223 }

nimbleNicMigrationFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NIC migration failed"
::= { traps 12224 }

nimbleNicPortUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NIC port is up"
::= { traps 12225 }

nimbleNicPortDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NIC port is down"
::= { traps 12226 }

nimbleIpDupFound NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Duplicate IP Address Detected"
::= { traps 12227 }

nimbleSubnetNicNegotiateIssue NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The data subnet NIC speed was not negotiated to its maximum possible speed"
::= { traps 12228 }

nimbleSubnetNicNegotiateNoIssue NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "All NICs in the subnet were negotiated correctly."
::= { traps 12229 }

nimbleSubnetNicMixSpeeds NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The data subnet has NICs with mixed speeds"
::= { traps 12230 }

nimbleSubnetNicSameSpeeds NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "All NICs within the subnet have the same speed."
::= { traps 12231 }

nimbleCtrlrNicAsymmetric NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The NIC count"
::= { traps 12232 }

nimbleCtrlrNicSymmetric NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The array Controllers are symmetrical"
::= { traps 12233 }

nimbleMtuMismatchFoundDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "MTU mismatch found"
::= { traps 12234 }

nimbleMtuMismatchResolvedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "MTU mismatch resolved"
::= { traps 12235 }

nimbleSensorLinearWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: Alert raised"
::= { traps 12301 }

nimbleSensorLinearClear NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: Alert cleared"
::= { traps 12302 }

nimbleSensorBoolWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: Alert raised"
::= { traps 12303 }

nimbleSensorBoolClear NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: Alert cleared"
::= { traps 12304 }

nimbleSensorDoesNotExist NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Sensor: is missing?:"
::= { traps 12305 }

nimbleNvramBattDisabledDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVRAM battery is disabled"
::= { traps 12306 }

nimbleNvramBattDisabledCritDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVRAM batteries are disabled"
::= { traps 12307 }

nimbleNvramBattOkDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVRAM battery is OK"
::= { traps 12308 }

nimbleTempSensorHighDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is warm"
::= { traps 12310 }

nimbleTempSensorLowDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is cold"
::= { traps 12311 }

nimbleTempSensorOkDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is ok"
::= { traps 12312 }

nimbleTempSensorMissingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor failed"
::= { traps 12313 }

nimbleTempSensorOperationalDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor is ok"
::= { traps 12314 }

nimbleFanSensorHighDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan in high speed"
::= { traps 12315 }

nimbleFanSensorLowDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan in low speed"
::= { traps 12316 }

nimbleFanSensorOkDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan is ok"
::= { traps 12317 }

nimbleFanSensorStoppedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan  stopped"
::= { traps 12318 }

nimbleFanSensorMissingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan missing"
::= { traps 12319 }

nimblePwrSupplySensorFailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply fail"
::= { traps 12320 }

nimblePwrSupplySensorMissingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply missing"
::= { traps 12321 }

nimblePwrSupplySensorOkDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply is ok"
::= { traps 12322 }

nimbleTempSensorHighDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is warm"
::= { traps 12323 }

nimbleTempSensorLowDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is cold"
::= { traps 12324 }

nimbleTempSensorOkDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is ok"
::= { traps 12325 }

nimbleTempSensorMissingDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor failed"
::= { traps 12326 }

nimbleTempSensorOperationalDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor is ok"
::= { traps 12327 }

nimbleFanSensorHighDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan in high speed"
::= { traps 12328 }

nimbleFanSensorLowDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan in low speed"
::= { traps 12329 }

nimbleFanSensorOkDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan is ok"
::= { traps 12330 }

nimbleFanSensorStoppedDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan  stopped"
::= { traps 12331 }

nimbleFanSensorMissingDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fan missing"
::= { traps 12332 }

nimblePwrSupplySensorFailDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply fail"
::= { traps 12333 }

nimblePwrSupplySensorMissingDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply missing"
::= { traps 12334 }

nimblePwrSupplySensorOkDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply is ok"
::= { traps 12335 }

nimbleTempSensorHighDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is warm"
::= { traps 12336 }

nimbleTempSensorLowDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is cold"
::= { traps 12337 }

nimbleTempSensorOkDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is OK"
::= { traps 12338 }

nimbleTempSensorMissingDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor failed"
::= { traps 12339 }

nimbleTempSensorOperationalDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Temperature sensor is OK"
::= { traps 12340 }

nimbleFanSensorHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan is at high speed"
::= { traps 12341 }

nimbleFanSensorLow NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan is at low speed"
::= { traps 12342 }

nimbleFanSensorOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan is OK"
::= { traps 12343 }

nimbleFanSensorStopped NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan  stopped"
::= { traps 12344 }

nimbleFanSensorMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fan missing"
::= { traps 12345 }

nimblePwrSupplySensorFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply fail"
::= { traps 12346 }

nimblePwrSupplySensorMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply missing"
::= { traps 12347 }

nimblePwrSupplySensorOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply is OK"
::= { traps 12348 }

nimblePsuIncorrect NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Incorrect power supply unit installed"
::= { traps 12349 }

nimblePsuOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply unit installed is OK."
::= { traps 12350 }

nimblePwrSupplySensorAcLoss NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply failed"
::= { traps 12351 }

nimblePwrSupplySensorFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply failed"
::= { traps 12352 }

nimbleTempSensorLow NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System temperature is cold"
::= { traps 12353 }

nimbleTempSensorOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System temperature is OK"
::= { traps 12354 }

nimbleTempSensorMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Temperature sensor failed"
::= { traps 12355 }

nimbleTempSensorOperational NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Temperature sensor is OK"
::= { traps 12356 }

nimbleNvramBattDisabled NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM battery is disabled"
::= { traps 12357 }

nimbleNvramBattDisabledCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM batteries are disabled"
::= { traps 12358 }

nimbleNvramBattOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM battery is OK"
::= { traps 12359 }

nimbleRaidDegraded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array degraded"
::= { traps 12400 }

nimbleRaidRebuildStart NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild started"
::= { traps 12401 }

nimbleRaidRebuildDone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild is done"
::= { traps 12402 }

nimbleRaidRebuildFailRead NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild failed"
::= { traps 12403 }

nimbleRaidRebuildFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild failed"
::= { traps 12404 }

nimbleRaidDisksMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disks missing from RAID array"
::= { traps 12405 }

nimbleRaidSpare NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk marked as spare"
::= { traps 12406 }

nimbleRaidAssemblyFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Could not assemble RAID array"
::= { traps 12407 }

nimbleRaidDegradedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array degraded"
::= { traps 12408 }

nimbleRaidRebuildStartV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild started"
::= { traps 12409 }

nimbleRaidRebuildDoneV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild is done"
::= { traps 12410 }

nimbleRaidRebuildFailReadV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild failed"
::= { traps 12411 }

nimbleRaidRebuildFailV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild failed"
::= { traps 12412 }

nimbleRaidDisksMissingV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disks missing from RAID array"
::= { traps 12413 }

nimbleRaidSpareV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk marked as spare"
::= { traps 12414 }

nimbleRaidAssemblyFailedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Could not assemble RAID array"
::= { traps 12415 }

nimbleRaidRebuildScheduledV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild scheduled"
::= { traps 12416 }

nimbleRaidRebuildStopV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array rebuild stopped"
::= { traps 12417 }

nimbleRaidRedundancy NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array redundancy"
::= { traps 12418 }

nimbleRaidDegradedForFwUpdate NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "RAID array degraded for firmware update"
::= { traps 12419 }

nimbleIscsiMultiInitiatorDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Multi initiator login"
::= { traps 12500 }

nimbleIscsiConnHardLimitDeprecated1 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Too many iscsi connections"
::= { traps 12501 }

nimbleIscsiUnalignedOpsDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Too many unaligned iscsi reads/writes"
::= { traps 12502 }

nimbleIscsiMultiInitiator NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Multi initiator login"
::= { traps 12503 }

nimbleIscsiConnHardLimitDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Too many iSCSI connections"
::= { traps 12504 }

nimbleIscsiUnalignedOps NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Too many unaligned iSCSI reads/writes"
::= { traps 12505 }

nimbleIscsiConnHardLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Too many iSCSI connections"
::= { traps 12506 }

nimbleIscsiErroneousItorConnsDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "iSCSI connections from initiator repeatedly closed by array due to improper target IP configuration"
::= { traps 12057 }

nimbleIscsiErroneousItorConns NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "iSCSI connections from initiator repeatedly closed by array due to improper target IP configuration"
::= { traps 12508 }

nimbleNvramBattCharging NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM battery is charging"
::= { traps 12601 }

nimbleNvramBattCharged NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM battery has finished charging"
::= { traps 12602 }

nimbleNvramFpgaVersion NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM version is incompatible"
::= { traps 12603 }

nimbleNvramMbeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVRAM card multi-bit error (MBE) detected"
::= { traps 12604 }

nimbleNvramSbeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVRAM card single-bit error (SBE) detected"
::= { traps 12605 }

nimbleNvramMbe NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM card non-correctable multi-bit error (MBE) detected"
::= { traps 12606 }

nimbleNvramSbe NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM card correctable single-bit error (SBE) detected"
::= { traps 12607 }

nimbleNvdimmReservedBlocksWarnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVDIMM reserved flash blocks reached the upper threshold"
::= { traps 12608 }

nimbleNvdimmReservedBlocksCritDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVDIMM reserved flash blocks reached the lower threshold"
::= { traps 12609 }

nimbleNvdimmUltracapDischargedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVDIMM ultracap cacapcitance discharged"
::= { traps 12610 }

nimbleNtbBadLink NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NTB_BAD_LINK"
::= { traps 12611 }

nimbleNvdimmUltracapDischargedDeprecated1 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVDIMM ultracap capacitance discharged"
::= { traps 12612 }

nimbleNvramMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVRAM module missing"
::= { traps 12613 }

nimbleNvdimmUltracapDischargedDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVDIMM ultracap capacitance discharged"
::= { traps 12614 }

nimbleEncryptionKeysMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Access to encrypted volumes denied"
::= { traps 12615 }

nimbleNvdimmUltracapDischargedDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "NVDIMM ultracap capacitance discharged"
::= { traps 12616 }

nimbleNvdimmReservedBlocksWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVDIMM reserved flash blocks reached the upper threshold"
::= { traps 12617 }

nimbleNvdimmReservedBlocksCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVDIMM reserved flash blocks reached the lower threshold"
::= { traps 12618 }

nimbleNvdimmUltracapDischarged NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "NVDIMM ultracap capacitance discharged"
::= { traps 12619 }

nimbleShelfCtrlrSide NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf controller connected to wrong side of host controller"
::= { traps 12701 }

nimbleShelfSesErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf SES device not ready"
::= { traps 12702 }

nimbleShelfDiskSasLink NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS link of a shelf slot is degraded"
::= { traps 12703 }

nimbleShelfDiskCountDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Not enough disk in shelf"
::= { traps 12704 }

nimbleShelfInvalidEeprom NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System cannot read shelf serial number"
::= { traps 12705 }

nimbleShelfWrongSasPortDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SAS cable connected to wrong port"
::= { traps 12706 }

nimbleShelfSasLink NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS link(s) between the shelves is(are) degraded"
::= { traps 12707 }

nimbleShelfSasExpErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS expander error"
::= { traps 12708 }

nimbleShelfCtrlrLoop NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf SAS loop detected"
::= { traps 12709 }

nimbleShelfMissing NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf appear only on one side of host controllers"
::= { traps 12710 }

nimbleShelfOrder NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf controller connection order mismatched"
::= { traps 12711 }

nimbleShelfSesMshipErrDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Cannot access shelf SES device"
::= { traps 12712 }

nimbleShelfFailoverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Controller failover due to shelf problem"
::= { traps 12713 }

nimbleShelfNewShelf NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "New Shelf detected"
::= { traps 12714 }

nimbleShelfDisconnect NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf is disconnected"
::= { traps 12715 }

nimbleShelfChassisSwap NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf chassis swap detected"
::= { traps 12716 }

nimbleShelfLocIdOverLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf daisy chain too long"
::= { traps 12717 }

nimbleShelfActivatedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "New shelf is activated"
::= { traps 12718 }

nimbleShelfReconnect NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Connection to shelf is restored"
::= { traps 12719 }

nimbleShelfSasLinkDisabledDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SAS link disabled"
::= { traps 12720 }

nimbleShelfDiskSasLinkErrDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Excessive link error on disk"
::= { traps 12721 }

nimbleShelfWrongSasPortDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SAS cable connected to wrong port"
::= { traps 12730 }

nimbleShelfSesMshipErrDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Cannot access shelf SES device"
::= { traps 12731 }

nimbleShelfSasLinkDisabled NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS link disabled"
::= { traps 12732 }

nimbleShelfDiskSasLinkErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive link error on disk"
::= { traps 12733 }

nimbleShelfWrongSasPortDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "SAS cable connected to wrong port"
::= { traps 12734 }

nimbleShelfSesMshipErrDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Cannot access shelf SES device"
::= { traps 12735 }

nimbleShelfSesMshipErrDeprecated4 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Cannot access shelf SES device"
::= { traps 12736 }

nimbleShelfActivatedV2Deprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "New shelf is activated"
::= { traps 12737 }

nimbleShelfSesMshipErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Cannot access shelf SES device"
::= { traps 12738 }

nimbleShelfActivatedV2 NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "New shelf activated"
::= { traps 12739 }

nimbleShelfIpmiMshipErr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Cannot access shelf IPMI device"
::= { traps 12740 }

nimbleShelfWrongSasPort NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SAS cable connected to wrong port"
::= { traps 12741 }

nimbleShelfBadDiskPhy NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive link errors between disk and expander"
::= { traps 12742 }

nimbleShelfBadInterconnectDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Shelf bad interconnect phy"
::= { traps 12743 }

nimbleShelfBadInterconnect NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive link errors between shelves"
::= { traps 12744 }

nimbleShelfDiskCount NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Too few disks in shelf"
::= { traps 12745 }

nimbleShelfBadCutlassDiskPhy NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Excessive link errors to disk"
::= { traps 12746 }

nimbleShelfEvacuationInitiated NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation initiated"
::= { traps 12747 }

nimbleShelfEvacuationComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation completed"
::= { traps 12748 }

nimbleShelfEvacuationPausedByUser NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation paused"
::= { traps 12749 }

nimbleShelfEvacuationResumedByUser NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation resumed"
::= { traps 12750 }

nimbleShelfEvacuationCancelByUser NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation canceled"
::= { traps 12751 }

nimbleShelfEvacuationFailSpaceUsage NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation paused due to high system utilization"
::= { traps 12752 }

nimbleShelfEvacuationFailSpaceRed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation paused due to low writable space"
::= { traps 12753 }

nimbleShelfEvacuationFailSpaceResume NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation resumed"
::= { traps 12754 }

nimbleShelfEvacuationFailSpaceRedResume NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation resumed"
::= { traps 12755 }

nimbleShelfEvacuationFailDataMove NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf evacuation failed while moving data"
::= { traps 12756 }

nimbleShelfCtrlrLoopNvmeof NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf loop detected"
::= { traps 12757 }

nimbleShelfMissingNvmeof NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf appear only on one side of host controllers"
::= { traps 12758 }

nimbleShelfReconnectNvmeof NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Connection to shelf is restored"
::= { traps 12759 }

nimbleShelfPciLinkSpeedLow NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf internal link speeds are lower than expected"
::= { traps 12760 }

nimbleShelfPciLinkSpeedNormal NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Shelf internal link speeds have returned to normal"
::= { traps 12761 }

nimblePhysMemMismatchDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Physical memory detected is less than installed"
::= { traps 12901 }

nimblePhysMemMismatch NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Physical memory detected is less than installed"
::= { traps 12902 }

nimbleVolSysLimitWarnEnter NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Total number of volumes approaching system limit"
::= { traps 13101 }

nimbleVolSysLimitWarnExit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Total number of volumes below warning threshold"
::= { traps 13102 }

nimbleGmTakeoverSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader role takeover succeeded"
::= { traps 13501 }

nimbleGmTakeoverSuccessDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader role takeover succeeded"
::= { traps 13504 }

nimbleGmTakeoverSuccessDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader role take over succeeded"
::= { traps 13505 }

nimbleGmMigrateFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Leader role migrate failed"
::= { traps 13506 }

nimbleGmTakeoverSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Management Service takeover succeeded"
::= { traps 13507 }

nimbleGmTakeoverFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Management Service takeover failed"
::= { traps 13508 }

nimbleGmSuccessfullySetupBgl NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Management Service is now highly available"
::= { traps 13509 }

nimbleGmNoBglAvailable NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Management Service is not highly available"
::= { traps 13510 }

nimbleGmBglOutOfSync NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Management Service Backup is no longer synchronized"
::= { traps 13511 }

nimbleGmGlSplitBrain NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Management Service ownership conflict"
::= { traps 13512 }

nimbleGmTakeoverRejectByArrayDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader role takeover has been rejected by a member array"
::= { traps 13502 }

nimbleGmTakeoverRejectByArrayDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Group Leader role takeover has been rejected by a member array"
::= { traps 13503 }

nimbleGmTakeoverAttempt NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Attempt to take over ownership of group Management Service"
::= { traps 13513 }

nimbleGmTakeoverNotifyLeaderRoleDelayDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Notification of group Management Service information to array delayed"
::= { traps 13514 }

nimbleGmTakeoverNotifyLeaderRoleComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Notification of group Management Service information to array completed"
::= { traps 13515 }

nimbleGmNoSmip NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "No secondary management IP configured"
::= { traps 13516 }

nimbleGmSmipConfigured NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Secondary management IP configured"
::= { traps 13517 }

nimbleGmSmipNotNeeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Secondary management IP not needed"
::= { traps 13518 }

nimbleGmBglInSync NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Management Service Backup is now synchronized"
::= { traps 13519 }

nimbleGmNoBglPossible NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group contains only the primary array for the Group Management Service"
::= { traps 13520 }

nimbleGmNoArrayFoundWithSameLimitAsGlDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Automatic failover of Group Management Service is unavailable"
::= { traps 13521 }

nimbleGmWitnessDisconnected NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Witness disconnected"
::= { traps 13522 }

nimbleGmWitnessConnected NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Witness connected"
::= { traps 13523 }

nimbleGmQuorumPeerFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Peer array disconnected"
::= { traps 13524 }

nimbleGmQuorumPeerSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Peer array connected"
::= { traps 13525 }

nimbleGmQuorumLocalFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Local array disconnected"
::= { traps 13526 }

nimbleGmQuorumLocalSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Local array connected"
::= { traps 13527 }

nimbleGmQuorumSetupFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Automatic failover of Group Management Service is unavailable"
::= { traps 13528 }

nimbleGmQuorumSetupSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Automatic failover of Group Management Service is now available"
::= { traps 13529 }

nimbleGmAutoShutoff NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group Management Service or Backup Group Management Service shutoff"
::= { traps 13530 }

nimbleGmQuorumWitnessUuidChangeDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Automatic failover of Group Management Service is unavailable"
::= { traps 13531 }

nimbleGmQuorumTeardownSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Automatic failover of Group Management Service is now disabled"
::= { traps 13532 }

nimbleGmTakeoverNotifyLeaderRoleDelay NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Notification of group Management Service information to array delayed"
::= { traps 13533 }

nimbleGmNoArrayFoundWithSameLimitAsGl NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Automatic failover of Group Management Service is unavailable due to a limit conflict"
::= { traps 13534 }

nimbleGmQuorumWitnessUuidChange NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Automatic failover of Group Management Service is unavailable due to a change in the witness configuration"
::= { traps 13535 }

nimbleGmGrpMrgDone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group merge completed successfully"
::= { traps 13601 }

nimbleGmGrpQscFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to stop services on source group for group merge"
::= { traps 13602 }

nimbleGmGrpMrgRollbackDone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Completed rollback of group merge operation"
::= { traps 13603 }

nimbleGmGrpMrgReassFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Group merge operation is not complete on some arrays"
::= { traps 13604 }

nimbleGmGrpMrgDbFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to merge configuration from source group"
::= { traps 13605 }

nimbleGmBinMigContAbortDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Data Migration is getting delayed because of continuous restarts"
::= { traps 13701 }

nimbleGmBinMigContAbortDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Data migration is delayed because of repeated restarts"
::= { traps 13702 }

nimbleGmBinMigContAbort NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Data migration is delayed because of repeated errors"
::= { traps 13703 }

nimbleCsmodelChanged NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "CS-Model changed"
::= { traps 14000 }

nimbleCsmodelUnknown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "CS-Model unknown"
::= { traps 14001 }

nimbleTempSensorHighDeprecated4 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "The system temperature is beginning to exceed the allowable operating temperature. If it continues to exceed allowed operating temperature"
::= { traps 14002 }

nimbleOvertempShutdownDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Controller shutdown occurred due to excessive temperature"
::= { traps 14003 }

nimbleCtrlrOvertemp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller exceeds allowable operating temperature"
::= { traps 14004 }

nimbleBackplaneOvertemp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Backplane exceeds allowable operating temperature"
::= { traps 14005 }

nimbleTempSensorHighDeprecated5 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature is too high."
::= { traps 14006 }

nimbleTempSensorCrithighDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "System temperature continues to be high."
::= { traps 14007 }

nimblePwrSupplySensorCallsupportDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply down revisioned"
::= { traps 14008 }

nimbleOvertempShutdown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Controller shutdown occurred due to excessive temperature"
::= { traps 14009 }

nimblePwrSupplySensorCallsupportDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply down revisioned"
::= { traps 14010 }

nimbleTempSensorHighDeprecated6 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array temperature is too high"
::= { traps 14011 }

nimbleTempSensorCrithighDeprecated1 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array temperature continues to be high"
::= { traps 14012 }

nimblePwrSupplySensorCallsupportDeprecated3 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply status unavailable"
::= { traps 14013 }

nimblePwrSupplySensorCallsupportDeprecated4 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Power supply status unavailable"
::= { traps 14014 }

nimbleTempSensorCrithighDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array temperature continues to be high"
::= { traps 14015 }

nimbleTempAmbientCrithigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array ambient temperature continues to be high"
::= { traps 14016 }

nimbleTempAmbientHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array ambient temperature continues to be high."
::= { traps 14017 }

nimbleTempAmbientOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array ambient temperature is approaching the safe operating temperature threshold"
::= { traps 14018 }

nimbleTempAmbientClear NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array ambient temperature is cooling down"
::= { traps 14019 }

nimbleTempSensorHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array temperature is too high"
::= { traps 14020 }

nimbleTempSensorCrithigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array temperature continues to be high"
::= { traps 14021 }

nimbleTempOvertempCrithigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array temperature continues to be high"
::= { traps 14022 }

nimbleTempOvertempOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "System temperature is OK"
::= { traps 14023 }

nimblePwrSupplySensorCallsupport NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Power supply status unavailable"
::= { traps 14024 }

nimbleUpdateUnknownFirmware NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "An unknown firmware version was detected"
::= { traps 14200 }

nimbleDiskFwUpdateStarted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk firmware update started"
::= { traps 14201 }

nimbleDiskFwUptodate NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk firmware up to date"
::= { traps 14202 }

nimbleDiskFwUpdateFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk firmware update failed"
::= { traps 14203 }

nimbleDiskFwUpdateDeferred NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Disk firmware update deferred"
::= { traps 14204 }

nimbleFcLinkUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel link up"
::= { traps 14400 }

nimbleFcLinkDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel link down"
::= { traps 14401 }

nimbleFcLinkNotConnected NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel link not connected"
::= { traps 14402 }

nimbleFcFabricUp NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel link up with connection to fabric"
::= { traps 14403 }

nimbleFcNoFabric NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel link up with no connection to fabric"
::= { traps 14404 }

nimbleFcHbaFailure NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel adapter failed"
::= { traps 14405 }

nimbleFcAsymmetricControllerConnectivityDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fibre Channel connectivty to controllers is asymmetric"
::= { traps 14406 }

nimbleFcAsymmetricControllerConnectivityOkDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Fibre Channel connectivty to controllers is symmetric"
::= { traps 14407 }

nimbleFcAsymmetricControllerConnectivity NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel connectivity to controllers is asymmetric"
::= { traps 14408 }

nimbleFcAsymmetricControllerConnectivityOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel connectivity to controllers is symmetric"
::= { traps 14409 }

nimbleFcPortLoginLimitExceeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel port login limit exceeded"
::= { traps 14410 }

nimbleFcTdzNotSupported NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel switch port does not support Target Driven Zoning"
::= { traps 14411 }

nimbleFcTdzNotEnabled NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Fibre Channel switch port does not have Target Driven Zoning enabled."
::= { traps 14412 }

nimbleFcPoorConnectivity NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Active controller has lost all Fibre Channel connectivity."
::= { traps 14413 }

nimbleEventPurgingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Oldest events removed from the system"
::= { traps 14700 }

nimbleEventWarnOverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Events count reached warning threshold"
::= { traps 14701 }

nimbleAuditLogPurgingDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Oldest audit log records removed from the system"
::= { traps 14702 }

nimbleAuditLogWarnOverDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Audit log records count reached warning threshold"
::= { traps 14703 }

nimbleEventPurging NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Oldest events removed from the system"
::= { traps 14704 }

nimbleEventWarnOver NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Events count reached warning threshold"
::= { traps 14705 }

nimbleAuditLogPurging NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Oldest audit log records removed from the system"
::= { traps 14706 }

nimbleAuditLogWarnOver NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Audit log records count reached warning threshold"
::= { traps 14707 }

nimbleAuditLogRootLoginSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Root Login succeeded."
::= { traps 14800 }

nimbleAuditLogRootLoginFailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Root Login failed."
::= { traps 14801 }

nimbleAdLocalPingFailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Active Directory client service on this group is not running"
::= { traps 14802 }

nimbleAdRemotePingFailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Active Directory Domain Controller is not reachable"
::= { traps 14803 }

nimbleAdTrustFailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Could not authenticate with Active Directory Domain Controller"
::= { traps 14804 }

nimbleAdCommunicationSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Successfully communicated with Active Directory Domain Controller"
::= { traps 14805 }

nimbleRootLoginSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Root login succeeded."
::= { traps 14806 }

nimbleRootLoginFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Root login failed."
::= { traps 14807 }

nimbleNsupportLoginSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Login by nsupport succeeded"
::= { traps 14808 }

nimbleNsupportLoginFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Login by nsupport failed"
::= { traps 14809 }

nimbleSuRootSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Elevating user privilege to root succeeded"
::= { traps 14810 }

nimbleSuRootFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Elevating user privilege to root failed"
::= { traps 14811 }

nimbleInvalidRoleLoginDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Login attempt by user without an assigned role"
::= { traps 14812 }

nimbleBglLoginSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Login to group Management Service backup array succeeded"
::= { traps 14813 }

nimbleBglLoginFailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Login to group Management Service backup array failed"
::= { traps 14814 }

nimbleBglLoginSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Login to group Management Service backup array succeeded"
::= { traps 14815 }

nimbleBglLoginFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Login to group Management Service backup array failed"
::= { traps 14816 }

nimbleTotpLoginSuccessful NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Successful support password time mode login. Recommend changing time mode secret."
::= { traps 14817 }

nimbleTotpSecretResetSuccessful NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Support password Time mode secret updated."
::= { traps 14818 }

nimbleVolDissocFromLockingProtectionSchedule NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume removed from volume collection with a lock period defined in its protection schedules"
::= { traps 14819 }

nimbleSchedWithLockPeriodDeleted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Protection schedule with lock period was removed"
::= { traps 14820 }

nimbleSchedWithLockPeriodDeletedOnHandover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Locking"
::= { traps 14821 }

nimbleSchedWithLockPeriodHaltedOnHandover NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Schedule replication to other partners halted as part of volume collection handover"
::= { traps 14822 }

nimbleLockPeriodRemovedFromProtsched NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Lock period on protection schedule removed"
::= { traps 14823 }

nimbleLockPeriodReducedOnProtsched NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Lock period on protection schedule reduced"
::= { traps 14824 }

nimbleDsdPinCacheDone NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Volume fully pinned in cache"
::= { traps 14850 }

nimbleDsdPinCacheDsdRestart NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Pinning of cache pinned volumes may have been affected by a Data Service restart"
::= { traps 14851 }

nimbleDsdPinCacheSsdIssue NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Pinning of cache pinned volumes may have been affected by an SSD loss"
::= { traps 14852 }

nimbleDsdPinCacheInternalError NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Pinning of cache pinned volumes may have been affected by an internal error"
::= { traps 14853 }

nimbleDsdPinCacheOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Blocks in any affected cache pinned volumes have been restored to cache"
::= { traps 14854 }

nimbleDsdPinCacheLowFdr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Pinning of cache pinned volumes has been affected by an SSD loss"
::= { traps 14855 }

nimbleArrayDedupeUtilizationOk NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Internal resource for data deduplication is back to normal"
::= { traps 14856 }

nimbleArrayDedupeUtilizationHigh NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Internal resource pressure is going to impact data deduplication efficiency"
::= { traps 14857 }

nimbleArrayDedupeUtilizationCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Internal resource pressure is now impacting data deduplication efficiency"
::= { traps 14858 }

nimbleAdTrustFailDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Could not authenticate with Active Directory Domain Controller."
::= { traps 14859 }

nimbleUnmanagedSnapDeleteSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unmanaged snapshot deletion succeeded"
::= { traps 14860 }

nimbleCertificateWarning NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "An SSL/TLS certificate is going to expire soon"
::= { traps 14861 }

nimbleCertificateExpired NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "An SSL/TLS certificate has expired"
::= { traps 14862 }

nimbleArrayFdrNormal NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array flash capacity is back to normal and sufficient for maximum data deduplication."
::= { traps 14863 }

nimbleArrayLowFdrWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array flash capacity is going to impact data deduplication efficiency."
::= { traps 14864 }

nimbleArrayLowFdrCrit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array flash capacity is now impacting data deduplication efficiency."
::= { traps 14865 }

nimbleArrayConfigFdrNormal NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array flash capacity is sufficient for maximum data deduplication"
::= { traps 14866 }

nimbleArrayConfigFdrLow NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array flash capacity is impacting the efficiency of data deduplication"
::= { traps 14867 }

nimbleArrayDedupeMinConfigRestore NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Current array configuration meets the minimum requirements needed for data deduplication"
::= { traps 14868 }

nimbleArrayDedupeMinFdr NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Current array configuration does not meet the minimum requirements for data deduplication"
::= { traps 14869 }

nimbleArrayDedupeMinSsdCount NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Current array configuration does not meet the minimum requirements for data deduplication"
::= { traps 14870 }

nimbleMaxSessionsLowMemPlat NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The group reached the maximum number of login sessions allowed on this platform."
::= { traps 14871 }

nimbleUserAcctAuthLockDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Too many failed authentication attempts caused the user account to be locked."
::= { traps 14872 }

nimbleMaxSessionsGroupDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "The group reached the maximum number of configured sessions."
::= { traps 14873 }

nimbleMaxSessionsLoginFailDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Login is blocked because the group reached the maximum number of configured sessions."
::= { traps 14874 }

nimbleSchedSrepSnapSucceededDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot succeeded."
::= { traps 14875 }

nimbleSchedSrepSnapSucceededUpstreamFailedDownstreamDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot succeeded but failed to synchronously replicate."
::= { traps 14876 }

nimbleSchedSrepSnapFailedUnknownReasonDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed."
::= { traps 14877 }

nimbleReplVolResynchronizationNeeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Some volumes that are synchronously replicating need resynchronization"
::= { traps 14878 }

nimbleInvalidRoleLogin NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Login attempt by user without an assigned role"
::= { traps 14879 }

nimbleUserAcctAuthLock NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Too many failed authentication attempts caused the user account to be locked"
::= { traps 14880 }

nimbleMaxSessionsGroup NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The group reached the maximum number of configured sessions"
::= { traps 14881 }

nimbleMaxSessionsLoginFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Login is blocked because the group reached the maximum number of configured sessions"
::= { traps 14882 }

nimbleSchedSrepSnapSucceeded NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot succeeded"
::= { traps 14883 }

nimbleSchedSrepSnapSucceededUpstreamFailedDownstreamDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot succeeded but failed to synchronously replicate"
::= { traps 14884 }

nimbleSchedSrepSnapFailedUnknownReasonDeprecated2 NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Scheduled snapshot failed"
::= { traps 14885 }

nimbleReplAbortedReplThrottledBandwidthZero NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication stopped"
::= { traps 14886 }

nimbleReplResumedReplThrottledBandwidthNonZero NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication resumed"
::= { traps 14887 }

nimbleExtKeyManagerOnline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Successfully communicated with external key manager."
::= { traps 14888 }

nimbleExtKeyManagerOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "External key manager is not reachable."
::= { traps 14889 }

nimbleAllowOldIqn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Allowing login to volume"
::= { traps 14890 }

nimbleExtKeyManagerInsufficientAccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Insufficient access to key manager to perform the operation."
::= { traps 14891 }

nimbleExtKeyManagerDown NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Encryption deactivated."
::= { traps 14892 }

nimbleApproachingMaxIscsiSessionLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Approaching maximum supported session count."
::= { traps 14893 }

nimbleExhaustedMaxIscsiSessionLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Reached maximum support session count."
::= { traps 14894 }

nimbleReplenishedMaxIscsiSessionLimit NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Below the maximum supported session count."
::= { traps 14895 }

nimbleAdTrustFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Could not authenticate with Active Directory Domain Controller."
::= { traps 14896 }

nimbleInvalidRoleLdapLogin NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Login attempt by LDAP service user failed"
::= { traps 14897 }

nimbleLdapDnsFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Could not resolve the address for any LDAP servers"
::= { traps 14898 }

nimbleLdapConnectFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Could not connect to any LDAP servers for domain"
::= { traps 14899 }

nimbleLdapTlsExpired NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSL/TLS certificate for the LDAP server has expired"
::= { traps 14900 }

nimbleLdapTlsNotTrusted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSL/TLS certificate for the LDAP server is not trusted"
::= { traps 14901 }

nimbleLdapTlsRevoked NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "SSL/TLS certificate for the LDAP server has been revoked"
::= { traps 14902 }

nimbleLdapTlsHostnameMismatch NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The hostname of the LDAP server does not match its SSL/TLS certificate"
::= { traps 14903 }

nimbleLdapTlsGeneralFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Unable to establish an SSL/TLS connection to the LDAP server"
::= { traps 14904 }

nimbleLdapBindFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Bind credentials were rejected by the LDAP server"
::= { traps 14905 }

nimbleLdapDomainOffline NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "An LDAP authentication error has occured"
::= { traps 14906 }

nimbleLdapTlsNotSupported NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "LDAP server does not support START TLS"
::= { traps 14907 }

nimbleLdapPermissionDenied NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The LDAP bind user has insufficient permissions"
::= { traps 14908 }

nimbleLdapAnonymousBindNotAllowed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "LDAP domain does not allow anonymous bind"
::= { traps 14909 }

nimbleSchedSrepSnapSucceededUpstreamFailedDownstream NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot succeeded but failed to synchronously replicate"
::= { traps 14910 }

nimbleSchedSrepSnapFailedUpstream NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Scheduled snapshot failed"
::= { traps 14911 }

nimbleReplAbortedReplCollectionToPartner NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Replication Aborted"
::= { traps 14912 }

nimbleMfaFailureForProtectedObject NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Failed to delete or change protected object"
::= { traps 14913 }

nimbleMfaProtectionRemovedFromObject NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Protection has been removed from object"
::= { traps 14914 }

nimbleArrayUpgradePrecheckFail NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array upgrade precheck failed"
::= { traps 15000 }

nimbleArrayUpgradeStarted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array upgrade started"
::= { traps 15001 }

nimbleArrayUpgradePaused NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array upgrade paused"
::= { traps 15002 }

nimbleArrayUpgradeResumed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array upgrade resumed"
::= { traps 15003 }

nimbleArrayUpgradeFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array upgrade failed"
::= { traps 15004 }

nimbleArrayUpgradeComplete NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array upgrade complete"
::= { traps 15005 }

nimbleArrayUpgradeAborting NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array upgrade abort in progress"
::= { traps 15006 }

nimbleArrayUpgradeAbortFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array upgrade abort failed"
::= { traps 15007 }

nimbleArrayUpgradeAborted NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array upgrade aborted"
::= { traps 15008 }

nimbleCloudConsoleActivationFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array activation from the activation portal failed."
::= { traps 16000 }

nimbleCloudConsoleActivationSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array successfully activated from the activation portal."
::= { traps 16001 }

nimbleCloudConsoleTunnnelConnectFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array connection to the cloud console failed."
::= { traps 16002 }

nimbleCloudConsoleTunnnelConnectSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array connected successfully to the cloud console"
::= { traps 16003 }

nimbleCloudConsoleSubscriptionCheckFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array subscription validation failed."
::= { traps 16004 }

nimbleCloudConsoleSubscriptionCheckSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array subscription valid."
::= { traps 16005 }

nimbleCloudConsoleDeviceRegistrationFailedDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array device registration/system session creation failed."
::= { traps 16006 }

nimbleCloudConsoleDeviceRegistrationSuccessDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array device registration and system session creation succeeded."
::= { traps 16007 }

nimbleCloudConsoleTunnnelConnectFailedInfoDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array connection to the cloud console failed."
::= { traps 16008 }

nimbleCloudConsoleActivationFailedWarnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array activation from the activation portal failed."
::= { traps 16009 }

nimbleCloudConsoleTunnnelConnectFailedWarnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array connection to the cloud console failed."
::= { traps 16010 }

nimbleCloudConsoleSubscriptionCheckFailedWarnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array subscription validation failed."
::= { traps 16011 }

nimbleCloudConsoleDeviceRegistrationFailedWarnDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array device registration/system session creation failed."
::= { traps 16012 }

nimbleCloudConsoleUsingExistingCloudInstanceDeprecated NOTIFICATION-TYPE
    OBJECTS{
        trapMsg,
        trapSeverity,
        trapOriginatorName,
        trapOriginatorSerialNumber,
        trapOriginatorGroupName,
        trapOriginatorGroupID,
        trapTarget,
        trapTargetType
    }
    STATUS obsolete
    DESCRIPTION
       "Array activation from the activation portal failed. Hence"
::= { traps 16013 }

nimbleCloudActivationFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array activation from the activation portal failed."
::= { traps 16014 }

nimbleCloudActivationSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array successfully activated from the activation portal."
::= { traps 16015 }

nimbleCloudTunnelConnectFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array connection to the cloud console failed."
::= { traps 16016 }

nimbleCloudTunnelConnectSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array connected successfully to the cloud console"
::= { traps 16017 }

nimbleCloudSubscriptionCheckFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array subscription validation failed."
::= { traps 16018 }

nimbleCloudSubscriptionCheckSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array subscription valid."
::= { traps 16019 }

nimbleCloudDeviceRegistrationFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array device registration/system session creation failed."
::= { traps 16020 }

nimbleCloudDeviceRegistrationSuccess NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array device registration and system session creation succeeded."
::= { traps 16021 }

nimbleCloudTunnelConnectFailedInfo NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array connection to the cloud console failed."
::= { traps 16022 }

nimbleCloudActivationFailedWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array activation from the activation portal failed."
::= { traps 16023 }

nimbleCloudTunnelConnectFailedWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array connection to the cloud console failed."
::= { traps 16024 }

nimbleCloudSubscriptionCheckFailedWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array subscription validation failed."
::= { traps 16025 }

nimbleCloudDeviceRegistrationFailedWarn NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array device registration/system session creation failed."
::= { traps 16026 }

nimbleCloudUsingExistingCloudInstance NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Array activation from the activation portal failed. Hence"
::= { traps 16027 }

nimbleCloudConsolePatchFailed NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The group could not send patch to the cloud console."
::= { traps 16028 }

nimbleCloudConsolePatchQueueFull NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "The group is unable to send all patches to the cloud console."
::= { traps 16029 }

nimbleCloudSupportEnabled NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Data Services Cloud Console support is enabled."
::= { traps 16030 }

nimbleCloudSupportDisabled NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Data Services Cloud Console support is disabled."
::= { traps 16031 }

nimbleCloudSupportEnabledInReadOnlyMode NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "Data Services Cloud Console support is enabled in a read_only mode."
::= { traps 16032 }

nimbleSrepNoWitnessConfig NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "For synchronous replication a witness should be connected to the Group Leader."
::= { traps 16033 }

nimbleOtpTimeSkew NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "OTP confirmation failed due to time skew."
::= { traps 16101 }

nimbleTestNoArgs NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "test"
::= { traps 150 }

nimbleTestOneArg NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "test"
::= { traps 151 }

nimbleTestTwoArgs NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "test"
::= { traps 152 }

nimbleTestThreeArgs NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "test"
::= { traps 153 }

nimbleTestFourArgs NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "test"
::= { traps 154 }

nimbleTestSevenArgs NOTIFICATION-TYPE
    OBJECTS{
        trapMsg,
        trapSeverity,
        trapOriginatorName,
        trapOriginatorSerialNumber,
        trapOriginatorGroupName,
        trapOriginatorGroupID,
        trapTarget,
        trapTargetType
    }
    STATUS current
    DESCRIPTION
       "test"
::= { traps 155 }

END
